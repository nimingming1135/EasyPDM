# -*- coding: utf-8 -*-
"""
EasyPDMDownload — makro FreeCAD do OTWIERANIA Części/Złożeń z EasyPDM (pobiera z serwera
i od razu otwiera w FreeCAD).

Instalacja / uruchomienie: dokładnie jak EasyPDMUpload.FCMacro — Macro -> Macros... ->
"Add path to macro path list", albo "Execute macro from file" bezpośrednio na tym pliku.
Logowanie i adres API są WSPÓLNE z EasyPDMUpload.FCMacro (te same preferencje FreeCAD,
User parameter:BaseApp/EasyPDM) — zalogowanie się w jednym makrze starcza dla obu. Makro
potrzebuje własnej sesji, mimo że wybór elementu zapada w przeglądarce — to ono odpytuje,
czy przeglądarka już skończyła (GET /api/create-tickets/{ticket}), i to ono ściąga same
pliki (GET /api/attachments/{id}/file) — przeglądarka tylko WSKAZUJE co pobrać, nie
przesyła żadnych bajtów. Ta sama sesja loguje przeglądarkę automatycznie (GET
/api/auth/browser-login) — jedno logowanie w makrze, nie dwa osobne.

Co robi:
    1. Natywne okno pyta TYLKO o folder docelowy (domyślnie podpowiada ostatnio użyty,
       zapamiętany w preferencjach FreeCAD, z przyciskiem "..." do zmiany) i pokazuje
       konto/Wyloguj — dokładnie jak "Wyślij do PDM" w EasyPDMUpload.FCMacro. WYBÓR,
       KTÓRĄ Część/Złożenie pobrać, zapada w PRZEGLĄDARCE SYSTEMOWEJ, nie tutaj: po
       zatwierdzeniu folderu makro od razu otwiera przeglądarkę, już zalogowaną (jednorazowy
       bilet logowania, nie sam token sesji makra), na pasku "oczekuje żądanie pobrania z makra CAD" (widoczny na
       każdym ekranie aplikacji webowej) z wyszukiwarką Części/Złożenia z CAŁEJ bazy (po
       numerze albo nazwie) — ten sam mechanizm co dogrywanie pliku do istniejącego
       elementu w EasyPDMUpload.FCMacro, tu użyty do wskazania "co pobrać". Po zatwierdzeniu
       w przeglądarce, FreeCAD (okno "Czekam na przeglądarkę", odpytujące co ~2s, limit
       10 minut) samo wykrywa wybór i pobieranie zaczyna się automatycznie — nie trzeba
       wracać do FreeCAD ręcznie. Anulowanie w przeglądarce/oknie oczekiwania kończy makro
       bez pobierania niczego.
    2. Dla Złożenia: pobiera też WSZYSTKIE jego składniki rekurencyjnie (bezpośrednie dzieci,
       potem ich dzieci, i tak dalej — cały BOM), do TEGO SAMEGO folderu co plik główny.
       Bez tego złożenie zbudowane na odnośnikach App::Link do zewnętrznych, zapisanych
       plików (standard w workbenchu Assembly/Assembly4) nie miałoby czym się otworzyć —
       FreeCAD rozwiązuje te odnośniki dopiero przy otwieraniu dokumentu, więc pliki
       składników muszą już leżeć na dysku PRZED otwarciem pliku głównego.
    3. Dla każdego pliku: jeśli w folderze docelowym jest już plik o DOKŁADNIE tej samej
       nazwie (czyli tej samej rewizji) i tym samym rozmiarze co na serwerze — pomija
       (nie pobiera drugi raz).
    4. Jeśli w folderze jest już plik tego samego elementu, ale w INNEJ (starszej) rewizji,
       a na serwerze jest nowsza — pyta, czy pobrać nowszą, zamiast cicho nadpisywać albo
       cicho zostawiać nieaktualny plik.
    5. Na końcu otwiera główny (wybrany) plik w FreeCAD (App.openDocument) — pliki składników
       zostają tylko na dysku, nie są automatycznie otwierane jako osobne dokumenty (dokładnie
       tak, jak FreeCAD sam otwiera złożenie: linkowane pliki wczytuje w tle, bez oddzielnych
       okien).

Skąd bierze pliki do pobrania:
    EasyPDM przechowuje AKTUALNY plik CAD Części/Złożenia jako załącznik (nie ma osobnego
    mechanizmu "plik elementu") — a przy KAŻDEJ wysyłce nowej rewizji poprzednia kopia
    ZOSTAJE (nowy załącznik obok starego, różne nazwy: "numer (nazwa).REWIZJA.rozszerzenie",
    ta sama konwencja co EasyPDMUpload.FCMacro), więc historia rewizji jest w praktyce
    odtwarzalna z listy załączników. To makro rozpoznaje tę konwencję, żeby trafić w
    załącznik odpowiadający AKTUALNEJ rewizji elementu (item["revisionNumber"]) — jeśli
    element nigdy nie przeszedł przez żadne makro CAD (np. dograny ręcznie w aplikacji
    webowej, więc załączniki mają dowolne, oryginalne nazwy), bierze po prostu najnowiej
    wgrany załącznik jako najlepsze przybliżenie.

Ograniczenia (świadomie poza zakresem pierwszej wersji):
    - Wybór elementu (punkt 1) wymaga, żeby domyślna przeglądarka systemowa umiała otworzyć
      adres serwera PDM (ten sam, co adres API w preferencjach makra) — na typowej
      instalacji (klient i serwer w tej samej sieci) działa to bez dodatkowej konfiguracji.
      Okno oczekiwania w FreeCAD ma limit 10 minut — po przekroczeniu (albo Anuluj) makro
      kończy się bez pobierania niczego.
    - Nie próbuje pobierać KONKRETNEJ starszej rewizji — zawsze celuje w aktualną, a starsze
      lokalne kopie służą tylko do wykrycia "masz nieaktualną wersję" (patrz punkt 4).
    - Wszystkie pliki (główny + składniki) lądują płasko w JEDNYM folderze, bez odtwarzania
      struktury BOM jako podfolderów — to najbezpieczniejszy wybór dla odnośników App::Link
      zapisanych jako ścieżki WZGLĘDEM folderu dokumentu (typowe dla Assembly4), ale jeśli
      oryginalny model był budowany z plikami w osobnych podfolderach, odnośniki mogą mimo
      to nie rozwiązać się automatycznie — wtedy trzeba je poprawić ręcznie w FreeCAD
      (Assembly4 ma do tego narzędzie "Make link relative"/zmianę ścieżki).
    - Współdzielony komponent (użyty w kilku miejscach drzewa) pobierany jest tylko raz
      (rozpoznawany po ID elementu), tak samo jak w EasyPDMUpload.FCMacro.
"""

import json
import os
import re
import shutil
import subprocess
import sys
import tempfile
import zipfile
import uuid
import webbrowser
from urllib import error, request
from urllib.parse import urlencode

import FreeCAD as App

try:
    from PySide6 import QtCore, QtWidgets
except ImportError:
    try:
        from PySide2 import QtCore, QtWidgets
    except ImportError:
        from PySide import QtCore
        from PySide import QtGui as QtWidgets  # bardzo stare FreeCAD (Qt4)


def _match_lang(raw):
    raw = (raw or "").strip().lower()
    if not raw:
        return None
    if raw.startswith("pl") or "polish" in raw or "polski" in raw:
        return "pl"
    if raw.startswith("de") or "german" in raw or "deutsch" in raw:
        return "de"
    if raw.startswith("en") or "english" in raw:
        return "en"
    if raw.startswith("zh") or "chinese" in raw or "中文" in raw:
        return "zh"
    return None


def _detect_language():
    """Auto-wykrycie języka: najpierw własne ustawienie FreeCAD (Preferences -> General ->
    Language) — bywa zapisane jako nazwa ("Polish"/"German") albo jako kod locale
    ("pl"/"pl_PL"/"de_DE" — stąd dopasowanie i po nazwie, i po prefiksie kodu), a jeśli to
    niejednoznaczne (pusty string albo coś spoza pl/en/de/zh), sprawdzamy locale systemu
    operacyjnego ($LANGUAGE/$LC_ALL/$LANG — na Linuksie zwykle "pl_PL.UTF-8"). Fallback na
    chiński (ten fork jest domyślnie chiński), gdy nic nie pasuje albo odczyt się nie powiedzie."""
    try:
        raw = App.ParamGet("User parameter:BaseApp/Preferences/General").GetString("Language", "")
    except Exception:
        raw = ""
    lang = _match_lang(raw)
    if lang:
        return lang
    raw_os = os.environ.get("LANGUAGE") or os.environ.get("LC_ALL") or os.environ.get("LANG") or ""
    return _match_lang(raw_os) or "zh"


LANG = _detect_language()


TRANSLATIONS = {
    "pl": {
        "no_connection": "Brak połączenia z {url}: {reason}",
        "login_failed_no_session": "Logowanie nie powiodło się — serwer nie zwrócił sesji.",
        "pdm_title": "PDM",
        "unnamed_fallback": "bez_nazwy",
        "easypdm_title": "EasyPDM",
        "easypdm_error_title": "EasyPDM — błąd",
        "login_dialog_title": "Logowanie do PDM",
        "api_address_label": "Adres API:",
        "username_label": "Nazwa użytkownika:",
        "password_label": "Hasło:",
        "login_button": "Zaloguj",
        "cancel_button": "Anuluj",
        "login_missing_fields": "Podaj nazwę użytkownika i hasło.",
        "download_folder_dialog_title": "Pobierz z PDM",
        "logged_in_as": "Zalogowano jako: {name}",
        "logout_button": "Wyloguj",
        "account_label": "Konto:",
        "target_dir_label": "Folder docelowy:",
        "choose_download_folder_caption": "Wybierz folder pobierania",
        "indicate_target_folder": "Wskaż folder docelowy.",
        "cannot_use_folder": "Nie można użyć tego folderu: {error}",
        "logged_out_message": "Wylogowano. Kolejne uruchomienie makra poprosi o ponowne zalogowanie.",
        "wait_timeout": "Upłynął czas oczekiwania.",
        "log_cancelled_not_opened": "Anulowano w przeglądarce — pobrane pliki zostały w folderze, dokument nie został otwarty.",
        "wait_ticket_status": "EasyPDM: czekam na wskazanie elementu w przeglądarce...",
        "log_no_attachments_list": "  {label}: nie udało się pobrać listy załączników ({error}).",
        "log_no_cad_files": "  {label}: brak plików CAD do pobrania (element nie ma żadnych załączników).",
        "log_wrong_format": (
            "  {label}: załącznik oznaczony jako plik CAD ma nieoczekiwane rozszerzenie "
            "\"{ext}\" (oczekiwano .FCStd) — pomijam, żeby nie próbować otworzyć niewłaściwego "
            "pliku ({fileName})."
        ),
        "log_already_present": "  {label}: już jest w folderze (aktualna rewizja), pomijam.",
        "log_relinked": "  {file}: przepiąłem odnośniki na pliki w tym folderze ({count}).",
        "log_relink_failed": "  {file}: nie udało się przepiąć odnośników ({error}) — otwórz i popraw ręcznie.",
        "newer_revision_title": "Nowsza rewizja",
        "newer_revision_body": (
            "W folderze jest już {label} w rewizji {rev_list}, a na serwerze aktualna "
            "jest rewizja {wanted}.\n\nPobrać najnowszą wersję?"
        ),
        "log_keeping_local_revision": "  {label}: zostawiam istniejącą lokalną rewizję ({rev_list}).",
        "log_downloading": "  Pobieram {file}...",
        "log_download_error": "  {label}: BŁĄD pobierania {file} ({error}).",
        "log_saved": "  Zapisano: {file}",
        "log_no_children_list": "  {label}: nie udało się pobrać listy składników ({error}).",
        "log_downloading_top": "Pobieram {number} ({name}) do {dir}...",
        "log_opened": "Otwarto: {path}",
        "log_open_failed": "Nie udało się otworzyć {path} w FreeCAD: {error}",
        "log_no_main_file": "Nie udało się ustalić pliku głównego do otwarcia.",
        "open_browser_failed": "Nie udało się otworzyć przeglądarki: {error}",
        "fetch_selected_item_failed": "Nie udało się pobrać danych wybranego elementu: {error}",
        "item_no_longer_exists": "Wybrany element już nie istnieje.",
        "download_interrupted": "Pobieranie przerwane nieoczekiwanym błędem:\n\n",
        "log_so_far": "\n\nDotychczasowy log:\n",
    },
    "en": {
        "no_connection": "Could not connect to {url}: {reason}",
        "login_failed_no_session": "Login failed — the server did not return a session.",
        "pdm_title": "PDM",
        "unnamed_fallback": "unnamed",
        "easypdm_title": "EasyPDM",
        "easypdm_error_title": "EasyPDM — Error",
        "login_dialog_title": "Log in to PDM",
        "api_address_label": "API address:",
        "username_label": "Username:",
        "password_label": "Password:",
        "login_button": "Log in",
        "cancel_button": "Cancel",
        "login_missing_fields": "Enter your username and password.",
        "download_folder_dialog_title": "Download from PDM",
        "logged_in_as": "Logged in as: {name}",
        "logout_button": "Log out",
        "account_label": "Account:",
        "target_dir_label": "Target folder:",
        "choose_download_folder_caption": "Choose download folder",
        "indicate_target_folder": "Choose a target folder.",
        "cannot_use_folder": "Cannot use this folder: {error}",
        "logged_out_message": "Logged out. The next time you run the macro, it will ask you to log in again.",
        "wait_timeout": "The waiting time has expired.",
        "log_cancelled_not_opened": "Cancelled in the browser — the files downloaded so far are in the folder; the document was not opened.",
        "wait_ticket_status": "EasyPDM: waiting for an item to be picked in the browser...",
        "log_no_attachments_list": "  {label}: failed to fetch the attachment list ({error}).",
        "log_no_cad_files": "  {label}: no CAD files to download (the item has no attachments).",
        "log_wrong_format": (
            "  {label}: the attachment marked as the CAD file has an unexpected extension "
            "\"{ext}\" (expected .FCStd) — skipping it rather than trying to open the wrong "
            "file ({fileName})."
        ),
        "log_already_present": "  {label}: already in the folder (current revision), skipping.",
        "log_relinked": "  {file}: links repointed to the files in this folder ({count}).",
        "log_relink_failed": "  {file}: could not repoint the links ({error}) — open and fix by hand.",
        "newer_revision_title": "Newer revision",
        "newer_revision_body": (
            "The folder already has {label} in revision {rev_list}, and the current "
            "revision on the server is {wanted}.\n\nDownload the newest version?"
        ),
        "log_keeping_local_revision": "  {label}: keeping the existing local revision ({rev_list}).",
        "log_downloading": "  Downloading {file}...",
        "log_download_error": "  {label}: ERROR downloading {file} ({error}).",
        "log_saved": "  Saved: {file}",
        "log_no_children_list": "  {label}: failed to fetch the list of children ({error}).",
        "log_downloading_top": "Downloading {number} ({name}) to {dir}...",
        "log_opened": "Opened: {path}",
        "log_open_failed": "Failed to open {path} in FreeCAD: {error}",
        "log_no_main_file": "Failed to determine the main file to open.",
        "open_browser_failed": "Failed to open the browser: {error}",
        "fetch_selected_item_failed": "Failed to fetch the selected item's data: {error}",
        "item_no_longer_exists": "The selected item no longer exists.",
        "download_interrupted": "Download interrupted by an unexpected error:\n\n",
        "log_so_far": "\n\nLog so far:\n",
    },
    "de": {
        "no_connection": "Keine Verbindung zu {url}: {reason}",
        "login_failed_no_session": "Anmeldung fehlgeschlagen — der Server hat keine Sitzung zurückgegeben.",
        "pdm_title": "PDM",
        "unnamed_fallback": "unbenannt",
        "easypdm_title": "EasyPDM",
        "easypdm_error_title": "EasyPDM — Fehler",
        "login_dialog_title": "Anmeldung bei PDM",
        "api_address_label": "API-Adresse:",
        "username_label": "Benutzername:",
        "password_label": "Passwort:",
        "login_button": "Anmelden",
        "cancel_button": "Abbrechen",
        "login_missing_fields": "Geben Sie Benutzername und Passwort ein.",
        "download_folder_dialog_title": "Von PDM herunterladen",
        "logged_in_as": "Angemeldet als: {name}",
        "logout_button": "Abmelden",
        "account_label": "Konto:",
        "target_dir_label": "Zielordner:",
        "choose_download_folder_caption": "Download-Ordner auswählen",
        "indicate_target_folder": "Wählen Sie einen Zielordner.",
        "cannot_use_folder": "Dieser Ordner kann nicht verwendet werden: {error}",
        "logged_out_message": "Abgemeldet. Beim nächsten Ausführen des Makros werden Sie erneut zur Anmeldung aufgefordert.",
        "wait_timeout": "Die Wartezeit ist abgelaufen.",
        "log_cancelled_not_opened": "Im Browser abgebrochen — die bisher heruntergeladenen Dateien liegen im Ordner, das Dokument wurde nicht geöffnet.",
        "wait_ticket_status": "EasyPDM: warte auf die Auswahl eines Elements im Browser...",
        "log_no_attachments_list": "  {label}: Anhangsliste konnte nicht abgerufen werden ({error}).",
        "log_no_cad_files": "  {label}: keine CAD-Dateien zum Herunterladen (das Element hat keine Anhänge).",
        "log_wrong_format": (
            "  {label}: der als CAD-Datei markierte Anhang hat eine unerwartete Erweiterung "
            "\"{ext}\" (erwartet .FCStd) — wird übersprungen, statt die falsche Datei zu "
            "öffnen ({fileName})."
        ),
        "log_already_present": "  {label}: bereits im Ordner vorhanden (aktuelle Revision), wird übersprungen.",
        "log_relinked": "  {file}: Verknüpfungen auf die Dateien in diesem Ordner umgehängt ({count}).",
        "log_relink_failed": "  {file}: Verknüpfungen konnten nicht umgehängt werden ({error}) — bitte von Hand korrigieren.",
        "newer_revision_title": "Neuere Revision",
        "newer_revision_body": (
            "Im Ordner befindet sich bereits {label} in Revision {rev_list}, und die "
            "aktuelle Revision auf dem Server ist {wanted}.\n\nSoll die neueste Version "
            "heruntergeladen werden?"
        ),
        "log_keeping_local_revision": "  {label}: die vorhandene lokale Revision wird beibehalten ({rev_list}).",
        "log_downloading": "  Lade {file} herunter...",
        "log_download_error": "  {label}: FEHLER beim Herunterladen von {file} ({error}).",
        "log_saved": "  Gespeichert: {file}",
        "log_no_children_list": "  {label}: Liste der Unterelemente konnte nicht abgerufen werden ({error}).",
        "log_downloading_top": "Lade {number} ({name}) nach {dir} herunter...",
        "log_opened": "Geöffnet: {path}",
        "log_open_failed": "{path} konnte nicht in FreeCAD geöffnet werden: {error}",
        "log_no_main_file": "Die zu öffnende Hauptdatei konnte nicht ermittelt werden.",
        "open_browser_failed": "Der Browser konnte nicht geöffnet werden: {error}",
        "fetch_selected_item_failed": "Die Daten des ausgewählten Elements konnten nicht abgerufen werden: {error}",
        "item_no_longer_exists": "Das ausgewählte Element existiert nicht mehr.",
        "download_interrupted": "Download durch einen unerwarteten Fehler unterbrochen:\n\n",
        "log_so_far": "\n\nBisheriges Protokoll:\n",
    },
    "zh": {
        "no_connection": "无法连接到 {url}：{reason}",
        "login_failed_no_session": "登录失败 —— 服务器未返回会话。",
        "pdm_title": "PDM",
        "unnamed_fallback": "未命名",
        "easypdm_title": "EasyPDM",
        "easypdm_error_title": "EasyPDM —— 错误",
        "login_dialog_title": "登录到 PDM",
        "api_address_label": "API 地址：",
        "username_label": "用户名：",
        "password_label": "密码：",
        "login_button": "登录",
        "cancel_button": "取消",
        "login_missing_fields": "请输入用户名和密码。",
        "download_folder_dialog_title": "从 PDM 下载",
        "logged_in_as": "已登录为：{name}",
        "logout_button": "退出登录",
        "account_label": "账户：",
        "target_dir_label": "目标文件夹：",
        "choose_download_folder_caption": "选择下载文件夹",
        "indicate_target_folder": "请选择目标文件夹。",
        "cannot_use_folder": "无法使用此文件夹：{error}",
        "logged_out_message": "已退出登录。下次运行宏时会再次要求登录。",
        "wait_timeout": "等待时间已超时。",
        "log_cancelled_not_opened": "已在浏览器中取消 —— 已下载的文件保留在文件夹中；文档未打开。",
        "wait_ticket_status": "EasyPDM：正在等待浏览器中选择条目……",
        "log_no_attachments_list": "   {label}：获取附件列表失败（{error}）。",
        "log_no_cad_files": "   {label}：没有可下载的 CAD 文件（该条目无附件）。",
        "log_already_present": "   {label}：已在文件夹中（当前版次），跳过。",
        "log_relinked": "   {file}：链接已重新指向本文件夹中的文件（{count} 个）。",
        "log_relink_failed": "   {file}：无法重新指向链接（{error}）—— 请手动打开并修复。",
        "newer_revision_title": "较新版次",
        "log_keeping_local_revision": "   {label}：保留本地现有版次（{rev_list}）。",
        "log_downloading": "   正在下载 {file}……",
        "log_download_error": "   {label}：下载 {file} 出错（{error}）。",
        "log_saved": "   已保存：{file}",
        "log_no_children_list": "   {label}：获取子组件列表失败（{error}）。",
        "log_downloading_top": "正在下载 {number}（{name}）到 {dir}……",
        "log_opened": "已打开：{path}",
        "log_open_failed": "无法在 FreeCAD 中打开 {path}：{error}",
        "log_no_main_file": "无法确定要打开的主文件。",
        "open_browser_failed": "打开浏览器失败：{error}",
        "fetch_selected_item_failed": "获取所选条目数据失败：{error}",
        "item_no_longer_exists": "所选条目已不存在。",
        "download_interrupted": "下载被意外错误中断：",
        "log_so_far": "\n已记录日志：\n",
        "log_wrong_format": "  {label}：标记为 CAD 文件的附件扩展名异常“{ext}”（预期 .FCStd）——跳过，避免打开错误的文件（{fileName}）。",
        "newer_revision_body": "文件夹中已有 {label} 的版次 {rev_list}，而服务器上的当前版次为 {wanted}。\n\n是否下载最新版本？",
    },
}


def t(key, **kwargs):
    text = TRANSLATIONS.get(LANG, TRANSLATIONS["en"]).get(key, TRANSLATIONS["en"].get(key, key))
    return text.format(**kwargs) if kwargs else text


# Ta sama grupa preferencji co EasyPDMUpload.FCMacro — adres API i sesja logowania są
# współdzielone między oboma makrami (zalogowanie się w jednym starcza dla drugiego).
PARAM_GROUP = "User parameter:BaseApp/EasyPDM"
DEFAULT_BASE_URL = "http://localhost:5000/api"
SESSION_COOKIE_NAME = "pdm_session"


class AuthError(RuntimeError):
    """Brak sesji albo sesja wygasła/została unieważniona."""
    pass


def get_base_url():
    return App.ParamGet(PARAM_GROUP).GetString("ApiBaseUrl", DEFAULT_BASE_URL).rstrip("/")


def set_base_url(url):
    App.ParamGet(PARAM_GROUP).SetString("ApiBaseUrl", url.rstrip("/"))


def get_session_token():
    token = App.ParamGet(PARAM_GROUP).GetString("SessionToken", "")
    return token or None


def set_session_token(token):
    App.ParamGet(PARAM_GROUP).SetString("SessionToken", token or "")


def get_saved_username():
    name = App.ParamGet(PARAM_GROUP).GetString("SavedDisplayName", "")
    return name or None


def set_saved_username(name):
    App.ParamGet(PARAM_GROUP).SetString("SavedDisplayName", name or "")


def get_download_folder():
    """Ostatnio użyty folder pobierania — osobna preferencja (nie dotyczy wysyłania),
    ale w tej samej grupie co reszta ustawień EasyPDM."""
    folder = App.ParamGet(PARAM_GROUP).GetString("DownloadFolder", "")
    return folder or None


def set_download_folder(folder):
    App.ParamGet(PARAM_GROUP).SetString("DownloadFolder", folder or "")


def open_in_browser(url):
    """Otwiera adres w przeglądarce tak, żeby wyszła NA WIERZCH.

    Dotąd było to `webbrowser.open`, który uruchamia po prostu `xdg-open`. Pod Wayland nowy
    proces dostaje fokus tylko wtedy, gdy uruchamiający przekaże mu token aktywacji
    (xdg-activation) — a `webbrowser` żadnego nie przekazuje. KDE otwierało więc kartę w tle
    i jedynie podświetlało przeglądarkę na pasku zadań; trzeba było ją wyciągać ręcznie
    (zgłoszone z praktyki, KDE/Wayland).

    `QDesktopServices.openUrl` robi to samo, ale przez Qt, który od wersji 6.6 prosi
    kompozytor o token w imieniu FreeCAD-a i przekazuje go dalej. Token jest ważny, bo
    w tej chwili fokus ma FreeCAD — użytkownik właśnie uruchomił w nim makro.

    `webbrowser.open` zostaje jako zapas: gdy Qt nie ma tej funkcji albo odmówi (stare
    FreeCAD, brak środowiska graficznego), zachowanie jest dokładnie takie jak dotąd."""
    try:
        try:
            from PySide6 import QtGui
        except ImportError:
            try:
                from PySide2 import QtGui
            except ImportError:
                from PySide import QtGui
        if QtGui.QDesktopServices.openUrl(QtCore.QUrl(url)):
            return
    except Exception:
        pass
    webbrowser.open(url)


# Pełny <title> aplikacji (EasyPDM.Web/index.html — musi się z nim zgadzać co do znaku).
# Okno przeglądarki dopasowujemy po POCZĄTKU
# tytułu, bo przeglądarki doklejają swoją nazwę na końcu. NIE po samym "EasyPDM": u autora
# okno Shotcuta miało w tytule "EasyPDM2.mlt", więc takie dopasowanie wyciągnęłoby na
# wierzch montaż wideo zamiast przeglądarki (wyłapane sondą na żywej sesji KDE).
APP_WINDOW_TITLE = "EasyPDM — CAD item browser"

# Skrypt dla KWin. Szuka zwykłego okna, którego tytuł zaczyna się od tytułu aplikacji, i
# aktywuje je. Plasma 6 ma windowList/activeWindow, Plasma 5 clientList/activeClient.
_KWIN_RAISE_SCRIPT = """
const wins = workspace.windowList ? workspace.windowList() : workspace.clientList();
for (const w of wins) {
    if (w.normalWindow && (%(match)s)) {
        if (workspace.activeWindow !== undefined) workspace.activeWindow = w;
        else workspace.activeClient = w;
        break;
    }
}
"""

# Okno FreeCAD-a: najpierw po numerze procesu, a gdy nie pasuje (FreeCAD z Flatpaka ma w
# piaskownicy inny pid niż ten, który widzi KWin) -- po klasie okna.
_KWIN_FREECAD_MATCH = (
    "w.pid === %(pid)d || !wins.some(function (x) { return x.normalWindow && x.pid === %(pid)d; })"
    " && (w.resourceClass || \"\").toLowerCase().indexOf(\"freecad\") >= 0"
)


def _raise_via_kwin(match_js=None):
    """Wyciąga okno przeglądarki na wierzch przez KWin — działa na KDE, także pod Wayland.

    Pod Wayland żadna aplikacja nie może sama aktywować okna innej. Może to jednak zrobić
    kompozytor, a KWin przyjmuje skrypty przez DBus (org.kde.KWin /Scripting) — tak samo
    działa `kdotool`. Skrypt jest zapisywany do pliku tymczasowego, wczytywany, uruchamiany i
    od razu zdejmowany.

    Potrzebne, bo token aktywacji (zob. open_in_browser) pomaga tylko przeglądarce
    URUCHAMIANEJ od zera. Gdy już działa, `xdg-open` startuje jedynie jej krótki proces
    pośredniczący, który przekazuje adres do działającego okna — a czy to okno skorzysta z
    tokenu, zależy od przeglądarki (zgłoszone z praktyki: zamknięta przeglądarka wychodziła na
    wierzch, otwarta — nie).

    `match_js` to warunek JS na oknie `w`; domyślnie okno przeglądarki z EasyPDM (po
    początku tytułu). Ten sam mechanizm wyciąga na wierzch sam FreeCAD -- zob.
    _show_on_top.

    Zwraca True, gdy skrypt udało się uruchomić — nie mówi, czy okno znalazł. Poza KDE (brak
    gdbus albo usługi org.kde.KWin) po prostu zwraca False."""
    if shutil.which("gdbus") is None:
        return False
    plugin = "easypdm-raise-browser"
    path = None

    def call(object_path, method, *args):
        return subprocess.run(
            ["gdbus", "call", "--session", "--dest", "org.kde.KWin",
             "--object-path", object_path, "--method", method, *args],
            capture_output=True, text=True, timeout=3,
        )

    try:
        fd, path = tempfile.mkstemp(prefix="easypdm-kwin-", suffix=".js")
        with os.fdopen(fd, "w", encoding="utf-8") as f:
            # json.dumps daje poprawny literał JS, z polskimi znakami jako \uXXXX.
            if match_js is None:
                match_js = '(w.caption || "").indexOf(%s) === 0' % json.dumps(APP_WINDOW_TITLE)
            f.write(_KWIN_RAISE_SCRIPT % {"match": match_js})
        # Gdyby poprzednie uruchomienie zostawiło skrypt wczytany, loadScript by odmówił.
        call("/Scripting", "org.kde.kwin.Scripting.unloadScript", plugin)
        loaded = call("/Scripting", "org.kde.kwin.Scripting.loadScript", path, plugin)
        found = re.search(r"-?\d+", loaded.stdout or "")
        if loaded.returncode != 0 or not found or int(found.group()) < 0:
            return False
        ran = call(f"/Scripting/Script{found.group()}", "org.kde.kwin.Script.run")
        call("/Scripting", "org.kde.kwin.Scripting.unloadScript", plugin)
        return ran.returncode == 0
    except Exception:
        return False
    finally:
        if path:
            try:
                os.remove(path)
            except OSError:
                pass


def _main_window():
    """Główne okno FreeCAD jako rodzic dla okien makra (None bez GUI)."""
    try:
        import FreeCADGui as Gui

        return Gui.getMainWindow()
    except Exception:
        return None


def _show_on_top(icon, title, text):
    """Komunikat, który wychodzi NA WIERZCH, także spod przeglądarki.

    Okna po wyborze elementu pojawiają się, gdy na wierzchu jest przeglądarka -- to w niej
    właśnie coś kliknięto. Okno bez rodzica lądowało pod nią (i pod samym FreeCAD-em), więc
    podsumowanie pobierania czekało niewidoczne, a nie było wiadomo, czy coś się jeszcze
    dzieje (zgłoszone przez użytkownika, KDE/Wayland). Pod Waylandem FreeCAD sam nie może
    wyjść przed inne okno, więc najpierw prosi o to KWin (jak przy przeglądarce, zob.
    _raise_via_kwin), a okno dostaje FreeCAD za rodzica -- menedżer okien trzyma je wtedy
    nad nim."""
    if sys.platform.startswith("linux"):
        _raise_via_kwin(_KWIN_FREECAD_MATCH % {"pid": os.getpid()})
    box = QtWidgets.QMessageBox(icon, title, text, QtWidgets.QMessageBox.Ok, _main_window())
    box.show()
    box.raise_()
    box.activateWindow()
    box.exec()


def _focus_browser_window():
    """Przenosi okno przeglądarki z EasyPDM na wierzch — odpowiednik `AppActivate "EasyPDM"`
    z makr SolidWorks/Inventor. Kopia (celowo zduplikowana,
    zob. LoginDialog) funkcji z EasyPDMUpload.FCMacro. Tylko dla Linuksa; na Windowsie nie ma tu czego naprawiać.

    Najpierw KWin (KDE, X11 i Wayland — zob. _raise_via_kwin), potem `wmctrl`/`xdotool`
    (inne środowiska pod X11). Poza tym — GNOME pod Wayland — nie zadziała nic, bo kompozytor
    na to nie pozwala; od strony przeglądarki czeka wtedy powiadomienie systemowe, którego
    kliknięcie przełącza na kartę."""
    if _raise_via_kwin():
        return True
    for command in (["wmctrl", "-a", APP_WINDOW_TITLE],
                    ["xdotool", "search", "--name", "^" + re.escape(APP_WINDOW_TITLE), "windowactivate"]):
        if shutil.which(command[0]) is None:
            continue
        try:
            done = subprocess.run(command, timeout=3,
                                  stdout=subprocess.DEVNULL, stderr=subprocess.DEVNULL)
            if done.returncode == 0:
                return True
        except Exception:
            pass
    return False


def build_browser_download_url(ticket):
    """Adres, pod którym otwiera się przeglądarka systemowa zamiast natywnej wyszukiwarki
    Części/Złożenia (zob. wait_for_ticket/main) — most logowania bilet->ciasteczko
    (GET /api/auth/browser-login) plus deep-link "?ticket=&mode=download"
    (pending-create-ticket.ts w aplikacji webowej) — "mode=download" mówi PendingTicketBanner,
    żeby od razu pokazać samą wyszukiwarkę (bez opcji "nowy element", nieistotnej przy
    pobieraniu) i pominąć checkbox STEP (dotyczy tylko wysyłania). Element wskazuje się przez
    POST /create-tickets/{ticket}/attach-existing — ten sam endpoint co przy dogrywaniu pliku
    w EasyPDMUpload.FCMacro, tu użyty do czystego wskazania "co pobrać", bez tworzenia ani
    zmieniania niczego. "ticket" w query stringu /auth/browser-login (bilet logowania,
    jednorazowy, świeżo pobrany z POST /auth/browser-bridge-ticket -- NIGDY sam token sesji,
    żeby ten nie lądował w historii przeglądarki) to inny byt niż "ticket" wewnątrz
    zakodowanego "redirect" (bilet korelacji wyboru elementu, argument tej funkcji). Frontend
    i API dzielą jeden origin, więc "redirect" to zawsze ścieżka względna zaczynająca się od
    "/" — dokładnie to, co GET /auth/browser-login akceptuje."""
    redirect_path = "/?" + urlencode({"ticket": ticket, "mode": "download"})
    login_ticket = api_post_json("/auth/browser-bridge-ticket", {})["ticket"]
    login_params = {"ticket": login_ticket, "redirect": redirect_path}
    return f"{get_base_url()}/auth/browser-login?{urlencode(login_params)}"


def _auth_headers():
    token = get_session_token()
    return {"Cookie": f"{SESSION_COOKIE_NAME}={token}"} if token else {}


def _read_error_body(http_error):
    try:
        return http_error.read().decode("utf-8") or str(http_error)
    except Exception:
        return str(http_error)


def _raise_for_http_error(e):
    if e.code == 401:
        raise AuthError(_read_error_body(e))
    raise RuntimeError(_read_error_body(e))


# ============================================================================
# Postęp pobierania pokazywany w aplikacji webowej jako lista plików odhaczana w trakcie
# (zob. TransferProgressStore.cs / TransferProgressPanel.tsx). Bliźniacze do tych samych
# funkcji w EasyPDMUpload.FCMacro.
#
# CELOWO nie korzysta z api_get: tamto rzuca wyjątkiem przy błędzie HTTP, a raportowanie
# postępu NIE MOŻE przerwać pobierania.
# ============================================================================

def _progress_send(method, path, payload):
    try:
        data = json.dumps(payload).encode("utf-8")
        headers = {"Content-Type": "application/json"}
        headers.update(_auth_headers())
        req = request.Request(get_base_url() + path, data=data, method=method, headers=headers)
        with request.urlopen(req, timeout=10):
            pass
    except Exception:
        pass


def progress_start(kind, entries):
    if not entries:
        return
    _progress_send("PUT", "/progress", {
        "kind": kind,
        "entries": [{"key": k, "label": l} for k, l in entries],
    })


def progress_mark(key, status):
    if key:
        _progress_send("PATCH", "/progress", {"key": key, "status": status})


# Użytkownik kliknął „Anuluj" w panelu postępu — zob. transfer_cancelled. Słownik, nie
# zwykła zmienna, żeby funkcje mogły go zmieniać bez `global`; przypisanie na poziomie modułu
# wykonuje się przy każdym uruchomieniu makra, więc stan nie przechodzi na kolejny bieg.
_CANCEL = {"requested": False}


def transfer_cancelled():
    """Czy użytkownik kliknął „Anuluj" w panelu postępu w przeglądarce.

    Serwer niczego sam nie przerywa — tylko zapisuje prośbę (POST /api/progress/cancel) — więc
    to makro pyta o nią przy każdym odpytaniu o formularz i przed każdym kolejnym plikiem. Plik,
    który akurat leci, zostaje dokończony: przerwanie w połowie zostawiłoby go uszkodzonego.

    Pierwsze „tak" jest zapamiętywane, żeby nie pytać serwera za każdym razem. Każdy błąd
    (brak połączenia, starszy serwer bez tego endpointu) znaczy „nie anulowano" — to wygoda,
    która nie ma prawa zatrzymać przesyłania."""
    if not _CANCEL["requested"]:
        try:
            probe = api_get("/progress/cancelled")
            if probe and probe.get("cancelled") == 1:
                _CANCEL["requested"] = True
                App.Console.PrintMessage(
                    "EasyPDM: anulowano w przegladarce -- zatrzymuje sie przed kolejnym plikiem\n"
                )
        except Exception:
            pass
    return _CANCEL["requested"]


def progress_finish():
    _progress_send("POST", "/progress/finish", {})


def api_get(path):
    req = request.Request(get_base_url() + path, method="GET", headers=_auth_headers())
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


def api_get_binary(path):
    """Jak api_get, ale zwraca surowe bajty odpowiedzi — do pobierania zawartości plików
    (załączników), które nie są JSON-em."""
    req = request.Request(get_base_url() + path, method="GET", headers=_auth_headers())
    try:
        with request.urlopen(req, timeout=120) as resp:
            return resp.read()
    except error.HTTPError as e:
        _raise_for_http_error(e)
    except error.URLError as e:
        raise RuntimeError(t("no_connection", url=get_base_url(), reason=e.reason))


def api_post_json(path, payload):
    data = json.dumps(payload).encode("utf-8")
    headers = {"Content-Type": "application/json"}
    headers.update(_auth_headers())
    req = request.Request(get_base_url() + path, data=data, method="POST", headers=headers)
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


def api_login(username, password):
    data = json.dumps({"username": username, "password": password}).encode("utf-8")
    req = request.Request(
        get_base_url() + "/auth/login", data=data, method="POST",
        headers={"Content-Type": "application/json"},
    )
    try:
        with request.urlopen(req, timeout=10) as resp:
            body = resp.read().decode("utf-8")
            user = json.loads(body) if body else {}
            set_cookie_header = resp.headers.get("Set-Cookie", "")
    except error.HTTPError as e:
        raise RuntimeError(_read_error_body(e))
    except error.URLError as e:
        raise RuntimeError(t("no_connection", url=get_base_url(), reason=e.reason))

    token = None
    for part in set_cookie_header.split(";"):
        part = part.strip()
        if part.startswith(f"{SESSION_COOKIE_NAME}="):
            token = part[len(SESSION_COOKIE_NAME) + 1:]
            break
    if not token:
        raise RuntimeError(t("login_failed_no_session"))

    set_session_token(token)
    set_saved_username(user.get("displayName") or user.get("username") or username)
    return user


def api_logout():
    token = get_session_token()
    if token:
        req = request.Request(
            get_base_url() + "/auth/logout", method="POST", headers=_auth_headers()
        )
        try:
            request.urlopen(req, timeout=10)
        except Exception:
            pass
    set_session_token(None)
    set_saved_username(None)


def ensure_logged_in():
    if get_session_token():
        try:
            me = api_get("/auth/me")
            # Odświeżamy zapisaną nazwę z /auth/me — bez tego, jeśli token pochodzi z sesji
            # zapisanej wcześniej BEZ przechodzenia przez api_login() w tej instalacji,
            # SavedDisplayName zostawałoby puste na zawsze mimo ważnej sesji — okno
            # pokazywałoby "Zalogowano jako: ?" (dokładnie tak, jak zaobserwowano w praktyce).
            if me:
                set_saved_username(me.get("displayName") or me.get("username"))
            return True
        except AuthError:
            set_session_token(None)
        except Exception:
            return True

    dlg = LoginDialog()
    return dlg.exec() == QtWidgets.QDialog.Accepted


def sanitize_filename(name):
    cleaned = re.sub(r'[\\/:*?"<>|]+', "_", name).strip()
    return cleaned or t("unnamed_fallback")


def revision_label(n):
    """Rewizje jako wielkie litery: 1->A, 2->B, ..., 26->Z, 27->AA... — ta sama konwersja
    co w EasyPDMUpload.FCMacro/api/types.ts (revisionLabel)."""
    n = int(n)
    label = ""
    while n > 0:
        n, remainder = divmod(n - 1, 26)
        label = chr(65 + remainder) + label
    return label or "A"


def _revision_attachment_pattern(item_number, name):
    """Regex dopasowujący własną konwencję nazewnictwa makr PDM: "numer (nazwa).REWIZJA."
    — grupa 1 to litera rewizji. Ta sama nazwa co nada EasyPDMUpload.FCMacro (zob. tam
    _rename_and_upload) — dzięki temu pobieranie i wysyłanie zawsze się zgadzają."""
    # [A-Za-z]*0* przed numerem: nazwa moze miec literowy prefiks rodzaju i zera wiodace
    # (Ustawienia -> Nazewnictwo), a zalaczniki wgrane przed wlaczeniem tych ustawien maja
    # sam numer -- oba warianty musza pasowac, inaczej pobieranie przestaloby widziec
    # wlasne starsze pliki.
    return re.compile(
        rf"^[A-Za-z]*0*{item_number}\s*(?:\({re.escape(sanitize_filename(name))}\))?\.([A-Za-z]+)\.",
        re.IGNORECASE,
    )


def _find_current_attachment(item, attachments):
    """Wybiera załącznik odpowiadający AKTUALNEJ rewizji elementu.

    Preferowana ścieżka: dokładne dopasowanie po item_attachments.revision_number --
    serwer oznacza nim każdy załącznik "cad"/"drawing" numerem rewizji elementu z chwili
    wgrania (migracja 049), więc to jest autorytatywne, bez zgadywania z nazwy pliku.
    Fallback (dla załączników wgranych PRZED istnieniem tej kolumny): dopasowanie po
    konwencji nazw makr PDM. Jeśli i to nie znajdzie nic (np. element dograny ręcznie w
    aplikacji webowej), bierze po prostu najnowiej wgrany załącznik (lista jest posortowana
    rosnąco po dacie) jako najlepsze przybliżenie.

    Rozważane są TYLKO załączniki z rolą "cad" (albo bez roli w ogóle -- starsze/ręcznie
    dograne pliki sprzed wprowadzenia ról, traktowane jako CAD dla wstecznej zgodności).
    Załączniki "step"/"pdf" to osobne eksporty do podglądu, nigdy pliki do otwarcia w CAD
    -- bez tego filtra powyższy fallback "najnowiej wgrany" mógł (i realnie potrafił, po
    dodaniu eksportu PDF, który wgrywa się na końcu) wybrać PDF zamiast właściwego pliku
    CAD, co kończyło się błędem przy próbie otwarcia go jako dokumentu FreeCAD."""
    attachments = [a for a in attachments if a.get("role") in (None, "cad")]
    if not attachments:
        return None

    wanted_revision = item.get("revisionNumber")
    if wanted_revision:
        for a in attachments:
            if a.get("revisionNumber") == wanted_revision:
                return a

    number = item.get("itemNumber")
    name = item.get("fileName", "")
    if number is not None:
        pattern = _revision_attachment_pattern(number, name)
        matches = []
        for a in attachments:
            m = pattern.match(a["fileName"])
            if m:
                matches.append((m.group(1), a))
        if matches:
            # Serwer wysyła gotowe "revisionLabel" obok "revisionNumber" (zob.
            # RevisionLabeling.cs) -- wolimy je od lokalnego przeliczenia, revision_label()
            # zostaje tylko jako fallback dla starszego serwera bez tego pola.
            wanted = (item.get("revisionLabel") or revision_label(item["revisionNumber"])).upper() if item.get("revisionNumber") else None
            for label, a in matches:
                if wanted and label.upper() == wanted:
                    return a
            return matches[-1][1]
    return attachments[-1]


def _local_revision_files(target_dir, item_number, name):
    """Lokalne pliki w target_dir pasujące do konwencji nazw TEGO elementu (dowolna
    rewizja) — do wykrycia "mam już starszą rewizję" (patrz _download_item)."""
    if item_number is None:
        return []
    pattern = _revision_attachment_pattern(item_number, name)
    result = []
    try:
        for fname in os.listdir(target_dir):
            m = pattern.match(fname)
            if m:
                result.append((m.group(1), os.path.join(target_dir, fname)))
    except OSError:
        pass
    return result


def _download_item(item, target_dir, log, downloaded=None):
    """Cienka nakładka na właściwe pobieranie, pilnująca wyłącznie listy postępu.

    Kluczem pozycji jest ID elementu — to samo, które zwrócił serwer w /descendants.
    Nakładka zamiast wstawek w środku, bo _download_item_inner ma pięć punktów wyjścia i
    może rzucić wyjątkiem; tutaj każda z tych ścieżek odhacza pozycję dokładnie raz, a
    nieudane pobranie zostaje na liście oznaczone jako błąd zamiast wisieć jako "w toku"."""
    progress_mark(item["id"], "active")
    try:
        result = _download_item_inner(item, target_dir, log)
        if result and downloaded is not None:
            downloaded.append(result)
    except Exception:
        progress_mark(item["id"], "failed")
        raise
    progress_mark(item["id"], "done" if result else "failed")
    return result


def _download_item_inner(item, target_dir, log):
    """Pobiera aktualny plik CAD Części/Złożenia `item` do target_dir (patrz reguły 3 i 4
    w docstringu modułu). Zwraca ścieżkę do pliku, który finalnie jest/zostaje w folderze
    (świeżo pobrany, już tam był, albo — gdy użytkownik odmówił pobrania nowszej rewizji —
    ta stara, którą i tak ma), albo None, jeśli nic nie udało się ustalić."""
    number = item.get("itemNumber")
    name = item.get("fileName", "")
    label = f"{item.get('itemNumberLabel') or number}({name})"

    try:
        attachments = api_get(f"/items/{item['id']}/attachments") or []
    except Exception as e:
        log(t("log_no_attachments_list", label=label, error=e))
        return None

    current = _find_current_attachment(item, attachments)
    if current is None:
        log(t("log_no_cad_files", label=label))
        return None

    # Dodatkowe zabezpieczenie NIEZALEŻNE od filtrowania po roli w _find_current_attachment
    # -- gdyby jednak trafił się załącznik z rolą "cad" (albo bez roli) o nieoczekiwanym
    # rozszerzeniu (np. ręcznie podmieniony w aplikacji webowej), makro odmawia otwarcia
    # go jako dokumentu FreeCAD zamiast wywalać się z niejasnym błędem natywnym.
    current_ext = os.path.splitext(current["fileName"])[1].lower()
    if current_ext != ".fcstd":
        log(t("log_wrong_format", label=label, ext=current_ext, fileName=current["fileName"]))
        return None

    target_path = os.path.join(target_dir, current["fileName"])

    if os.path.exists(target_path):
        try:
            same_size = os.path.getsize(target_path) == current.get("fileSize")
        except OSError:
            same_size = False
        if same_size:
            log(t("log_already_present", label=label))
            return target_path

    older = [
        (rev, path)
        for rev, path in _local_revision_files(target_dir, number, name)
        if path != target_path
    ]
    if older:
        rev_list = ", ".join(sorted({rev for rev, _ in older}))
        wanted = (item.get("revisionLabel") or revision_label(item["revisionNumber"])) if item.get("revisionNumber") else "?"
        answer = QtWidgets.QMessageBox.question(
            None,
            t("newer_revision_title"),
            t("newer_revision_body", label=label, rev_list=rev_list, wanted=wanted),
            QtWidgets.QMessageBox.Yes | QtWidgets.QMessageBox.No,
        )
        if answer != QtWidgets.QMessageBox.Yes:
            log(t("log_keeping_local_revision", label=label, rev_list=rev_list))
            return older[0][1] if len(older) == 1 else None

    log(t("log_downloading", file=current["fileName"]))
    try:
        content = api_get_binary(f"/attachments/{current['id']}/file")
    except Exception as e:
        log(t("log_download_error", label=label, file=current["fileName"], error=e))
        return None

    os.makedirs(target_dir, exist_ok=True)
    with open(target_path, "wb") as f:
        f.write(content)
    log(t("log_saved", file=current["fileName"]))
    return target_path


def _flatten_xlinks(file_paths, log):
    """Przepina odnośniki App::Link na pliki leżące OBOK, w tym samym folderze.

    Pobieranie kładzie wszystko płasko w jednym folderze, ale złożenie pamięta ścieżkę
    sprzed wysyłki — jeśli komponenty były wtedy w podfolderze, w pliku zostaje
    `<XLink file="test/8(1ddd).A.FCStd" .../>`. FreeCAD rozwiązuje to WZGLĘDEM folderu
    złożenia, czyli szuka w `.../test/test/...` i zgłasza "Link not restored" oraz
    "Link broken!". Zgłoszone z praktyki: pobrane złożenie otwierało się bez komponentów.

    .FCStd to archiwum ZIP, a ścieżki odnośników to atrybut `file` elementów `<XLink>`
    w Document.xml. Obcinamy z nich katalog — i TYLKO wtedy, gdy plik o tej nazwie
    faktycznie leży w tym samym folderze. Dzięki temu odnośnik, którego nie pobraliśmy
    (coś spoza tego drzewa), zostaje nietknięty zamiast zostać wskazany w próżnię.

    Zapis idzie przez plik tymczasowy i dopiero potem podmianę, żeby przerwanie w trakcie
    nie zostawiło uszkodzonego dokumentu. Każdy błąd jest połykany: to naprawa wygody, a nie
    część pobierania — nieudana nie może wywrócić tego, co już się udało ściągnąć."""
    pattern = re.compile(rb'(<XLink\b[^>]*?\bfile=")([^"]+)(")')
    repaired_total = 0

    for path in file_paths:
        if not path or not path.lower().endswith(".fcstd") or not os.path.exists(path):
            continue
        folder = os.path.dirname(path)
        try:
            with zipfile.ZipFile(path, "r") as zf:
                entries = [(i, zf.read(i.filename)) for i in zf.infolist()]
        except Exception as e:
            log(t("log_relink_failed", file=os.path.basename(path), error=e))
            continue

        changed = 0

        def fix(m):
            nonlocal changed
            stored = m.group(2).decode("utf-8", "replace")
            base = os.path.basename(stored.replace("\\", "/"))
            # Już płaski albo nie mamy takiego pliku obok -- nie ruszamy.
            if stored == base or not os.path.exists(os.path.join(folder, base)):
                return m.group(0)
            changed += 1
            return m.group(1) + base.encode("utf-8") + m.group(3)

        new_entries = []
        for info, data in entries:
            if info.filename.lower().endswith(".xml"):
                data = pattern.sub(fix, data)
            new_entries.append((info, data))

        if changed == 0:
            continue

        try:
            tmp = path + ".easypdm-relink"
            with zipfile.ZipFile(tmp, "w", zipfile.ZIP_DEFLATED) as zf:
                for info, data in new_entries:
                    zf.writestr(info.filename, data)
            os.replace(tmp, path)
            repaired_total += changed
            log(t("log_relinked", file=os.path.basename(path), count=changed))
        except Exception as e:
            try:
                os.remove(tmp)
            except Exception:
                pass
            log(t("log_relink_failed", file=os.path.basename(path), error=e))

    return repaired_total


def _download_children_recursive(item, target_dir, log, seen, downloaded=None):
    """Rekurencyjnie pobiera CAŁE drzewo składników Złożenia (bezpośrednie dzieci, potem
    ich dzieci, itd.) do target_dir — patrz punkt 2 w docstringu modułu. `seen` (zbiór ID
    elementów) chroni przed podwójnym pobraniem tego samego, współdzielonego komponentu."""
    try:
        rows = api_get(f"/items/{item['id']}/children") or []
    except Exception as e:
        label = f"{item.get('itemNumberLabel') or item.get('itemNumber')}({item.get('fileName')})"
        log(t("log_no_children_list", label=label, error=e))
        return
    # UWAGA: odpowiedź to lista {"item": {...}, "quantity": ..., "position": ...} — sam
    # element jest ZAGNIEŻDŻONY pod kluczem "item" (ta sama konwencja co childEntries
    # w item-detail-panel.tsx), NIE płaski obiekt jak w GET /api/items.
    for row in rows:
        # Anulowanie z przeglądarki: stop PRZED kolejnym plikiem. Powrót z rekurencji trafia
        # w pętli rodzica znowu tutaj i dostaje zapamiętaną odpowiedź — tak schodzi całość.
        if transfer_cancelled():
            return
        child = row["item"]
        if child["id"] in seen:
            continue
        seen.add(child["id"])
        _download_item(child, target_dir, log, downloaded)
        if child["itemType"] == "assembly":
            _download_children_recursive(child, target_dir, log, seen, downloaded)


class LoginDialog(QtWidgets.QDialog):
    """Identyczne okno logowania co w EasyPDMUpload.FCMacro (współdzielona sesja, ale
    dwa osobne pliki makr — FreeCAD nie ma niezawodnego sposobu importowania jednego
    makra z drugiego, więc kod jest świadomie zduplikowany, nie importowany)."""

    def __init__(self, parent=None):
        super().__init__(parent)
        self.setWindowTitle(t("login_dialog_title"))
        self.setMinimumWidth(360)

        layout = QtWidgets.QVBoxLayout(self)
        form = QtWidgets.QFormLayout()
        layout.addLayout(form)

        self.server_edit = QtWidgets.QLineEdit(get_base_url())
        form.addRow(t("api_address_label"), self.server_edit)

        self.username_edit = QtWidgets.QLineEdit()
        form.addRow(t("username_label"), self.username_edit)

        self.password_edit = QtWidgets.QLineEdit()
        self.password_edit.setEchoMode(QtWidgets.QLineEdit.Password)
        form.addRow(t("password_label"), self.password_edit)

        self.error_label = QtWidgets.QLabel("")
        self.error_label.setStyleSheet("color: #c0392b;")
        self.error_label.setWordWrap(True)
        layout.addWidget(self.error_label)

        buttons = QtWidgets.QDialogButtonBox(
            QtWidgets.QDialogButtonBox.Ok | QtWidgets.QDialogButtonBox.Cancel
        )
        buttons.button(QtWidgets.QDialogButtonBox.Ok).setText(t("login_button"))
        buttons.button(QtWidgets.QDialogButtonBox.Cancel).setText(t("cancel_button"))
        buttons.accepted.connect(self._try_login)
        buttons.rejected.connect(self.reject)
        layout.addWidget(buttons)

    def _try_login(self):
        self.error_label.setText("")
        set_base_url(self.server_edit.text().strip())
        username = self.username_edit.text().strip()
        password = self.password_edit.text()
        if not username or not password:
            self.error_label.setText(t("login_missing_fields"))
            return
        try:
            api_login(username, password)
        except Exception as e:
            self.error_label.setText(str(e))
            return
        self.accept()


class DownloadFolderDialog(QtWidgets.QDialog):
    """Jedyne natywne okno w całym przebiegu main() — pyta o folder docelowy (gdzie mają
    wylądować pobrane pliki) i pokazuje konto/Wyloguj. Wybór KTÓREGO elementu pobrać zapada
    w przeglądarce (zob. build_browser_download_url/main) — folder to jedyna rzecz, której
    przeglądarka nie może sama ustalić (wybór lokalnego miejsca zapisu wymaga natywnego
    okna systemowego)."""

    def __init__(self, parent=None):
        super().__init__(parent)
        self.result_folder = None

        self.setWindowTitle(t("download_folder_dialog_title"))
        self.setMinimumWidth(440)

        outer = QtWidgets.QVBoxLayout(self)
        form = QtWidgets.QFormLayout()
        outer.addLayout(form)

        account_row = QtWidgets.QHBoxLayout()
        self.account_label = QtWidgets.QLabel(t("logged_in_as", name=get_saved_username() or "?"))
        account_row.addWidget(self.account_label)
        logout_btn = QtWidgets.QPushButton(t("logout_button"))
        logout_btn.clicked.connect(self.on_logout)
        account_row.addWidget(logout_btn)
        account_row.addStretch(1)
        form.addRow(t("account_label"), account_row)

        folder_row = QtWidgets.QHBoxLayout()
        self.folder_edit = QtWidgets.QLineEdit(get_download_folder() or "")
        folder_row.addWidget(self.folder_edit)
        browse_btn = QtWidgets.QPushButton("...")
        browse_btn.setMaximumWidth(32)
        browse_btn.clicked.connect(self.on_browse)
        folder_row.addWidget(browse_btn)
        form.addRow(t("target_dir_label"), folder_row)

        self.error_label = QtWidgets.QLabel("")
        self.error_label.setStyleSheet("color: #c0392b;")
        self.error_label.setWordWrap(True)
        outer.addWidget(self.error_label)

        buttons = QtWidgets.QDialogButtonBox(
            QtWidgets.QDialogButtonBox.Ok | QtWidgets.QDialogButtonBox.Cancel
        )
        buttons.accepted.connect(self.on_submit)
        buttons.rejected.connect(self.reject)
        outer.addWidget(buttons)

    def on_logout(self):
        api_logout()
        QtWidgets.QMessageBox.information(
            self, t("pdm_title"), t("logged_out_message")
        )
        self.reject()

    def on_browse(self):
        start = self.folder_edit.text().strip() or os.path.expanduser("~")
        chosen = QtWidgets.QFileDialog.getExistingDirectory(self, t("choose_download_folder_caption"), start)
        if chosen:
            self.folder_edit.setText(chosen)

    def on_submit(self):
        self.error_label.setText("")
        folder = self.folder_edit.text().strip()
        if not folder:
            self.error_label.setText(t("indicate_target_folder"))
            return
        try:
            os.makedirs(folder, exist_ok=True)
        except OSError as e:
            self.error_label.setText(t("cannot_use_folder", error=e))
            return
        set_download_folder(folder)
        self.result_folder = folder
        self.accept()


def wait_for_ticket(ticket, timeout_seconds=600, raise_browser=False):
    """Czeka, aż element zostanie wskazany w przeglądarce — BEZ własnego okna. Odpowiednik
    (celowo zduplikowany, zob. LoginDialog wyżej) funkcji o tej samej nazwie w
    EasyPDMUpload.FCMacro, gdzie stoi też pełne wyjaśnienie.

    W skrócie: okno „Czekam na przeglądarkę" powstawało zaraz po tym, jak przeglądarka
    dostała fokus, i Qt odbierało jej go z powrotem, przez co lista elementów lądowała ZA
    FreeCAD-em. Makra SolidWorks i Inventor nie mają tu żadnego okna — czekają, pisząc na
    pasku stanu, i tak jest teraz również tutaj.

    Zwraca dane biletu albo None, gdy upłynął czas oczekiwania."""
    import time

    status_bar = None
    try:
        import FreeCADGui as Gui

        status_bar = Gui.getMainWindow().statusBar()
        status_bar.showMessage(t("wait_ticket_status"))
    except Exception:
        status_bar = None

    try:
        deadline = time.time() + timeout_seconds
        polls = 0
        while time.time() < deadline:
            try:
                data = api_get(f"/create-tickets/{ticket}")
                if data and data.get("itemId"):
                    return data
            except Exception:
                # Chwilowy błąd sieci nie przerywa czekania — kolejny obieg spróbuje ponownie.
                pass

            # Przeglądarka otwarta przed chwilą przez open_in_browser: gdy już działała, nowa
            # karta mogła wylądować w tle (zob. _raise_via_kwin). Wyciągamy ją przy pierwszych
            # trzech odpytaniach — strona potrzebuje chwili, żeby załadować się i ustawić tytuł,
            # po którym okno jest rozpoznawane. Tylko trzy, żeby nie wyrywać fokusu komuś, kto
            # świadomie wrócił do FreeCAD-a.
            if raise_browser and polls < 3 and sys.platform.startswith("linux"):
                _focus_browser_window()
            polls += 1

            # Interfejs odświeżany dziesięć razy częściej niż odpytywanie serwera, żeby
            # FreeCAD nie stał zamrożony przez cały czas czekania.
            for _ in range(20):
                try:
                    QtWidgets.QApplication.processEvents()
                except Exception:
                    pass
                time.sleep(0.1)

        App.Console.PrintMessage(f"EasyPDM: {t('wait_timeout')}\n")
        return None
    finally:
        if status_bar is not None:
            try:
                status_bar.clearMessage()
            except Exception:
                pass

def _run_download(top_item, target_dir, log):
    """Faktyczne pobieranie + otwarcie, wydzielone z main() wyłącznie po to, żeby dało się
    je owinąć w jeden szeroki try/except (zob. main()) — błąd, którego nie przewidzieliśmy
    (np. nieoczekiwany kształt odpowiedzi API), ma się skończyć CZYTELNYM komunikatem
    z pełnym tracebackiem, a nie cichym zniknięciem makra bez żadnego okna na końcu
    (dokładnie to przydarzyło się w praktyce, zanim doszło to zabezpieczenie — zob. też
    poprawiony _download_children_recursive, gdzie leżała PIERWOTNA przyczyna)."""
    log(t("log_downloading_top", number=top_item["itemNumber"], name=top_item["fileName"], dir=target_dir))

    seen = {top_item["id"]}

    # Lista do panelu postępu. W odróżnieniu od wysyłki makro NIE zna jej z góry —
    # _download_children_recursive schodzi poziom po poziomie i w tym momencie nie wie, ile
    # plików będzie. Dlatego pytamy serwer o całe poddrzewo jednym zapytaniem; deduplikacja
    # po jego stronie odpowiada tej po "seen" tutaj, więc liczby się zgadzają.
    try:
        rows = api_get(f"/items/{top_item['id']}/descendants") or []
        progress_start("download",
                       [(r["id"], r.get("recordName") or r.get("fileName", "")) for r in rows])
    except Exception:
        pass

    downloaded = []
    top_path = _download_item(top_item, target_dir, log, downloaded)
    if top_item["itemType"] == "assembly":
        _download_children_recursive(top_item, target_dir, log, seen, downloaded)

    progress_finish()

    # Odnośniki muszą wskazywać na pliki leżące OBOK — wszystko pobraliśmy do jednego
    # folderu, więc ścieżka z podfolderem sprzed wysyłki rozwiązałaby się w próżnię.
    # Robione PRZED otwarciem dokumentu: po otwarciu FreeCAD ma już zepsute odnośniki
    # wczytane i samo przepisanie pliku na dysku niczego by nie naprawiło.
    _flatten_xlinks(downloaded, log)

    # Anulowane z przeglądarki: pobrane pliki zostają na dysku, ale dokumentu NIE otwieramy —
    # bez reszty komponentów złożenie otworzyłoby się z brakującymi odnośnikami.
    if _CANCEL["requested"]:
        log(t("log_cancelled_not_opened"))
        return

    if top_path and os.path.exists(top_path):
        try:
            App.openDocument(top_path)
            log(t("log_opened", path=top_path))
        except Exception as e:
            log(t("log_open_failed", path=top_path, error=e))
    else:
        log(t("log_no_main_file"))


def main():
    if not ensure_logged_in():
        return

    # Jedyne natywne okno w całym przebiegu — folder docelowy + konto. KTÓRY element
    # pobrać wybiera się w przeglądarce (zob. build_browser_download_url), nie tutaj.
    folder_dialog = DownloadFolderDialog()
    if folder_dialog.exec() != QtWidgets.QDialog.Accepted:
        return
    target_dir = folder_dialog.result_folder

    ticket = str(uuid.uuid4())
    try:
        url = build_browser_download_url(ticket)
        open_in_browser(url)
    except Exception as e:
        QtWidgets.QMessageBox.critical(None, t("pdm_title"), t("open_browser_failed", error=e))
        return

    ticket_data = wait_for_ticket(ticket, raise_browser=True)
    if ticket_data is None:
        # Upłynął czas oczekiwania — nic do pobrania.
        return

    try:
        top_item = api_get(f"/items/{ticket_data['itemId']}")
    except Exception as e:
        _show_on_top(QtWidgets.QMessageBox.Critical, t("pdm_title"), t("fetch_selected_item_failed", error=e))
        return
    if top_item is None:
        _show_on_top(QtWidgets.QMessageBox.Critical, t("pdm_title"), t("item_no_longer_exists"))
        return

    log_lines = []

    def log(msg):
        log_lines.append(msg)
        App.Console.PrintMessage(msg + "\n")

    try:
        _run_download(top_item, target_dir, log)
    except Exception:
        import traceback

        tb = traceback.format_exc()
        App.Console.PrintError(tb + "\n")
        _show_on_top(
            QtWidgets.QMessageBox.Critical,
            t("easypdm_error_title"),
            t("download_interrupted")
            + tb
            + t("log_so_far")
            + "\n".join(log_lines[-15:]),
        )
        return

    # Po „Anuluj" w przeglądarce bez okna na koniec — raport z biegu jest już w powiadomieniach,
    # tam, gdzie kliknięto. Zapis przebiegu został w Report View.
    if _CANCEL["requested"]:
        return
    _show_on_top(QtWidgets.QMessageBox.Information, t("easypdm_title"), "\n".join(log_lines[-25:]))


if __name__ == "__main__":
    main()
